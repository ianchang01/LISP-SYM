(defun *error* (msg)
  (if oldla (setvar "clayer" oldla))
  (if oldos (setvar "osmode" oldos))
  (setvar "attreq" 1)
  (setvar "attdia" 1)
  (prompt msg)
)

(defun get_csv ()
  (cond ((= ans "1") (setq ff (getfiled "選擇新設圖面的.CSV檔案" start_path "csv" 2)))
	((= ans "2") (setq ff (getfiled "選擇新設圖面的.XLS檔案" start_path "xls" 2)))
	((= ans "3") (setq ff (getfiled "選擇新設圖面的.XLSX檔案" start_path "xlsx" 2))) 
  )
  (cond ((not ff) (exit))
	((= ans "1") (do_csv))
	((= ans "2") (do_xls))
	((= ans "3") (do_xls))
	(t (alert "請選擇.CSV或.XLS檔案") (get_csv))
  )
)

(defun do_csv() 
  (setq str_list nil dno_list nil #dno_list nil)
  (setq fr (open ff "r"))
  (read-line fr)
  (read-line fr)
  (while (setq str (read-line fr))
    (setq $n (vl-string-search "," str))
    (setq #1 (substr str 1 $n))
    (setq str (substr str (+ $n 2)))
    (setq $n (vl-string-search "," str))
    (setq #2 (substr str 1 $n))
    (setq str (substr str (+ $n 2)))
    (setq $n (vl-string-search "," str))
    (setq #3 (substr str 1 $n))
    (setq str (substr str (+ $n 2)))
    (setq $n (vl-string-search "," str))
    (setq #4 (substr str 1 $n))
    (setq str (substr str (+ $n 2)))
    (repeat 8
      (setq $n (vl-string-search "," str))
      (setq str (substr str (+ $n 2)))
    )
    (setq $n (vl-string-search "," str))
    (setq #5 (substr str 1 $n))
    (setq str_list (append str_list (list (list #2 #1 #3 #4 #5))))
    (setq dno_list (append dno_list (list #2)))
    (setq ##1 #1)
    (repeat (- 12 (strlen #1))
      (setq ##1 (strcat ##1 " "))
    )	    
    (setq #dno_list (append #dno_list (list (strcat ##1 #2))))
  )
  (close fr)
  (princ)
)

(defun chg_dash()
  (setq ## "")
  (setq #n 1)
  (repeat (strlen #1)
    (setq #chr (substr #1 #n 1))
    (if (= #chr "-") (setq #chr "_"))
    (setq ## (strcat ## #chr))
    (setq #n (1+ #n))
  )
  (setq #1 ##)
)    

(defun do_xls() 
  (setq str_list nil dno_list nil #dno_list nil)
  (setq xls_file ff)
  (IniciaExcel "SHEET2")
  (setq row 6) ;;3->6
  (while (and (setq #2 (datocelda row 6)) (/= #2 ""))  ;col=2判斷 2->6
    (setq #1  (datocelda row 4))   ;1->4
    (setq #3  (datocelda row 7))   ;3->7
    (setq #4  (datocelda row 17))  ;4->17
    (setq #5  (datocelda row 11))  ;13->11
    (if (= (type #1) 'REAL) (setq #1 (rtos #1)))
    (chg_dash) ;;-改為_
    (if (= (type #5) 'REAL) (setq #5 (rtos #5)))
    (setq str_list (append str_list (list (list #2 #1 #3 #4 #5))))
    (setq dno_list (append dno_list (list #2)))
    (setq ##1 #1)
    (repeat (- 12 (strlen #1))
      (setq ##1 (strcat ##1 " "))
    )	    
    (setq #dno_list (append #dno_list (list (strcat ##1 #2))))
    (setq row (1+ row))
  )
  (vlax-invoke-method (vlax-get-property objExcel "ActiveWorkbook") "Close" :vlax-False)
  (TerminaExcel)
  (princ)
)


(defun get_list (#no)
  (setq begin (assoc #no str_list)) ;;找到此編號
  (if (not begin) (progn (alert (strcat "找不到編號: " #no " 的資料。")) (exit))) 
  (setq key (strcat (nth 1 begin) "_"))
  (setq slen (strlen key))
  (setq find_list (cdr (member begin str_list)))
  (setq ans_list nil $chk t $n 0 chk_list nil)
  (while (and (< $n (length find_list)) $chk)
    (setq data (nth $n find_list))
    (setq ##no (nth 1 data))
    (if (= (substr ##no 1 slen) key)
        (if (not (vl-string-search "_" (substr ##no (1+ slen))))
	    (if (not (member ##no chk_list))
	        (setq ans_list (append ans_list (list data))
		      chk_list (append chk_list (list ##no)))
	        (setq $chk nil)
	    )
	)
    )
    (setq $n (1+ $n))
  )  
)

(defun chg_factor()
  (setq ent (entlast))
  (if (> #len 27)
      (setq wfac 0.4)
      (setq wfac (cadr (assoc #len wfac_list)))
  )
  (repeat 3 (setq ent (entnext ent)))
  (setq data (entget ent))
  (setq old (assoc 41 data))
  (setq new (cons 41 wfac))
  (entmod (subst new old data))
)


(defun chg_factor2()
  (if (> #len 27)
      (setq wfac 0.4)
      (setq wfac (cadr (assoc #len wfac_list)))
  )
  (repeat 3 (setq ent (entnext ent)))
  (setq data (entget ent))
  (setq old (assoc 41 data))
  (setq new (cons 41 wfac))
  (entmod (subst new old data))
)

(defun chg_factor3()
  (setq ent (entlast))
  (cond ((>  #len 23) (setq wfac2 0.28))
        ((>= #len 11) (setq wfac2 (cadr (assoc #len wfac2_list))))
	(t (setq wfac2 nil))
  )
  (if wfac2
    (progn
      (setq data (entget ent))
      (setq old (assoc 41 data))
      (setq new (cons 41 wfac2))
      (entmod (subst new old data))
    )  
  )  
)

(defun get_border()
  (setq bor_list nil)
  (setq ff (findfile "border.txt"))
  (setq fr (open ff "r"))
  (while (setq str (read-line fr))
    (setq $n (vl-string-search "," str))
    (setq #1 (substr str 1 $n))
    (setq str (substr str (+ $n 2)))
    (setq $n (vl-string-search "," str))
    (setq #2 (atof (substr str 1 $n)))
    (setq #3 (atof (substr str (+ $n 2))))
    (setq bor_list (append bor_list (list (list #1 #2 #3))))
  )
  (close fr)
)  

(defun get_basept()
  (setq #blk nil)
  (foreach x bor_list
    (if (setq ss (ssget "x" (list (cons 0 "INSERT") (cons 2 (setq tmp (car x)))))) (setq #blk tmp blk_list x #ss ss))
  )
  (if (not #blk)
      (progn
	(initget 7)
	(setq pt (getpoint "\nBOM表插入點： "))
      )
      (progn
	(setq p0 (cdr (assoc 10 (entget (ssname #ss 0)))))
	(setq pt (list (+ (car p0) (nth 1 blk_list)) (+ (cadr p0) (nth 2 blk_list))))
      )  
  )
)

(defun chk_bom()
  (setq ss_old (ssget "x" '((0 . "INSERT") (2 . "BOM_*"))))
  (if ss_old
     (progn
       (initget "Yes No")
       (setq ans (getkword "\n資料已存在，是否刪除原資料? Yes/No: "))
       (if (= ans "No")
	   (exit)
       )
     )
  )  
)	
  
(defun fill_list(key xx_list)
  (start_list key)
  (mapcar 'add_list xx_list)
  (end_list)
)

(defun c:get_bom()
  (setvar "cmdecho" 0)
  (command ".ucs" "w")
  (get_border)
  (load "w_factor")
  (chk_bom)
  (setq oldla (getvar "clayer"))
  (setq oldos (getvar "osmode"))
  (initget "1 2 3")
  (setq ans (getkword "\n(1).csv/(2).xls(3).xlsx<1>: "))
  (if (not ans) (setq ans "1"))
  (get_csv)
  (if (not (setq ss_no (ssget "x" '((0 . "INSERT") (2 . "DRAWING-NO")))))
      (setq #dno "")
      (progn
	(setq n 0 #dno "")
	(repeat (sslength ss_no)
	  (setq ent (ssname ss_no n))
	  (setq $dno (cdr (assoc 1 (entget (entnext ent)))))
	  (if (= $dno "") (setq $dno (cdr (assoc 1 (entget (entnext ent))))))
	  (if (/= $dno "") (setq #dno (substr $dno 1 9)))
          (setq n (1+ n))
	)
      )
  )
  (if (= #dno "")
      (if (not (setq ss_no (ssget "x" '((0 . "INSERT") (2 . "A#BORDER")))))
	  (setq #dno "")
	  (progn
	    (setq ent (ssname ss_no 0))
	    (setq blk (strcase (cdr (assoc 2 (entget ent)))))
	    (setq obj (vlax-ename->vla-object ent)) 
            (vla-GetBoundingBox obj 'ptmin 'ptmax)
            (setq ptmin (vlax-safearray->list ptmin))
            (setq ptmax (vlax-safearray->list ptmax))
	    (setq p1 (list (car ptmax) (cadr ptmin)))
	    (if (= blk "A0BORDER")
	        (setq p2 (list (- (car p1) 84) (+ (cadr p1) 18.45)))
	        (setq p2 (list (- (car p1) 74) (+ (cadr p1) 18.45)))
	    )  
            (setq sst (ssget "w" p1 p2 '((0 . "TEXT"))))
	    (if (not sst)
	        (setq #dno "")
	        (setq #dno (substr (cdr (assoc 1 (entget (ssname sst 0)))) 1 9))
	    )
	  )
       )	
  )
  (setq dcl_id (load_dialog "get_bom.dcl"))
  (new_dialog "get_bom" dcl_id)
  (set_tile "dno" #dno)
  (fill_list "$dno" #dno_list)
  (if (/= #dno "") (focus_item))
  (action_tile "dno"   "(focus_item)")
  (action_tile "$dno"   "(set_tile \"dno\" (nth (atoi $value) dno_list))")
  (action_tile "accept" "(setq #dno (get_tile \"dno\")) (done_dialog 1)")
  (action_tile "cancel" "(done_dialog 0)")
  (setq ans (start_dialog))
  (if (= ans 1) (get_bom))
  (setvar "clayer" oldla)
  (setvar "osmode" oldos)
  (setvar "attdia" 1)
  (princ)
)

(defun focus_item()
  (setq #find (strcase (vl-string-right-trim " " (get_tile "dno"))))
  (setq #len (strlen #find))
  (setq go t #m 0)
  (while (and go (< #m (length dno_list)))
    (if (= (substr (nth #m dno_list) 1 #len) #find)
        (setq go nil)
        (setq #m (1+ #m))
    )
  )
  (if go
      (alert "找不到此編號!")
      (set_tile "$dno" (itoa #m))
  )   
)	       


(defun get_bom()
  (get_list #dno)
  ;;(setq pt (getpoint "\nBOM表插入點： "))
  (get_basept)
  (command ".erase" ss_old "")
  (if (tblsearch "LAYER" "TEXT")
      (setvar "clayer" "TEXT")
      (command ".layer" "m" "TEXT" "c" 3 "TEXT" "")
  )
  (setvar "osmode" 0)
  (setvar "attdia" 0)
  (command ".insert" "BOM_Title" pt 1 1 0)
  (setq pt (polar pt (* 0.5 pi) 8))
  (setq #n 1)
  (foreach item ans_list
    (command ".insert" "BOM_item" pt 1 1 0 (itoa #n) (nth 0 item) (setq #val (nth 2 item)) (nth 4 item) (nth 3 item))
    (if (> (setq #len (strlen #val)) 15) (chg_factor)) 
    (setq #n (1+ #n))
    (setq pt (polar pt (* 0.5 pi) 8))
  )  
)

(defun get_att_list()
  (setq all_att_list nil)
  (setq n 0)
  (repeat (sslength ss_item)
    (setq ent0 (ssname ss_item n))
    (setq att_list nil ent ent0)
    (setq ent (entnext ent))
    (setq data (entget ent))
    
    (setq #1 nil #2 nil #3 nil #4 nil #5 nil)
    (while (= (cdr (assoc 0 data)) "ATTRIB")
      (setq tag (cdr (assoc 2 data)))
      (setq val (cdr (assoc 1 data)))
      (cond ((= tag "NO")   (setq #1 val))
	    ((= tag "DNO")  (setq #2 val))
	    ((= tag "NAME") (setq #3 val))
	    ((= tag "QTY")  (setq #4 val))
            ((= tag "SIZE") (setq #5 val))
      )
      (setq ent (entnext ent))
      (setq data (entget ent))
    )
    (if (and #1 #2 #3 #4 #5)
        (setq all_att_list (append all_att_list (list (list #2 #1 #3 #4 #5 ent0))))
    )  
    (setq n (1+ n))
  )
  (setq all_att_list (vl-sort all_att_list '(lambda (s1 s2) (< (atoi (cadr s1)) (atoi (cadr s2))))))
)


;;==================================================================================================
(defun IniciaExcel($sheet)
  (vl-load-com)
  (setq ObjExcel (vlax-create-object "Excel.Application"))
  (setq ObjWorkbooks (vlax-get-property ObjExcel "workbooks"))
  (setq ObjCurrWorkbooks (vlax-invoke-method ObjWorkbooks "open" xls_file))
  (setq ObjSheets (vlax-get-property ObjCurrWorkbooks "Sheets"))
  (setq item 1 ObjSheet nil)
  (repeat (vlax-get-property ObjSheets "count")
    (setq CurSheet (vlax-get-property ObjSheets "Item" item))
    ;(if (= (strcase (vlax-get-property CurSheet "Name")) "SHEET2") (setq ObjSheet CurSheet))
    (if (= (strcase (vlax-get-property CurSheet "Name")) $sheet) (setq ObjSheet CurSheet))
    (setq item (1+ item))
  )
  (if (not ObjSheet) (progn (alert (strcat "找不到 " $Sheet)) (TerminaExcel) (exit)))
  (setq ObjCells (vlax-get-property ObjSheet "cells"))
)

(defun IniciaExcel2()
  (vl-load-com)
  (setq ObjExcel (vlax-create-object "Excel.Application"))
  (setq ObjWorkbooks (vlax-get-property ObjExcel "workbooks"))
  (setq ObjCurrWorkbooks (vlax-invoke-method ObjWorkbooks "open" xls_file))
  (setq ObjSheets (vlax-get-property ObjCurrWorkbooks "Sheets"))
  (setq ObjSheet (vlax-get-property ObjSheets "Item" 1))
  (setq ObjCells (vlax-get-property ObjSheet "cells"))
)

(defun TerminaExcel()
  (if ObjCells (vlax-release-object ObjCells))
  (if ObjSheet (vlax-release-object ObjSheet))
  (vlax-release-object ObjSheets)
  (vlax-release-object ObjCurrWorkbooks)
  (vlax-release-object ObjWorkbooks)
  (vlax-release-object ObjExcel)
)

(defun DatoCelda (row col)
   (vlax-variant-value (vlax-get-property
   (vlax-variant-value (vlax-get-property ObjCells 'Item row col)) 'Value))
)

(defun get_ec_excel()
  (setq ff (findfile "ec.txt"))
  (setq fr (open ff "r"))
  ;(setq str "階層,D")
  (while (setq str (read-line fr))
    (cond ((vl-string-search "階層" str)       (setq col1 (- (ascii (vl-string-right-trim " " (strcase (substr str (strlen str))))) 64)))
	  ((vl-string-search "設變前零件" str) (setq col2 (- (ascii (vl-string-right-trim " " (strcase (substr str (strlen str))))) 64)))
	  ((vl-string-search "設變後零件" str) (setq col3 (- (ascii (vl-string-right-trim " " (strcase (substr str (strlen str))))) 64)))
	  ((vl-string-search "零件名稱" str)   (setq col4 (- (ascii (vl-string-right-trim " " (strcase (substr str (strlen str))))) 64)))
	  ((vl-string-search "設變前數量" str) (setq col5 (- (ascii (vl-string-right-trim " " (strcase (substr str (strlen str))))) 64)))
	  ((vl-string-search "設變後數量" str) (setq col6 (- (ascii (vl-string-right-trim " " (strcase (substr str (strlen str))))) 64)))
	  ((vl-string-search "圖面" str)       (setq col7 (- (ascii (vl-string-right-trim " " (strcase (substr str (strlen str))))) 64)))
    )	   
  )
  (close fr)
  (setq xls_file (getfiled "選擇設變的Excel檔案" start_path "xls*" 4))
  (IniciaExcel "SHEET2")
  (setq row 6)
  (setq xls_list nil #dno_list nil dno_list nil)
  (while (and (setq sno (datocelda row col1)) (/= sno ""))  ;col=4判斷
    (setq #no1  (datocelda row col2))
    (if (not #no1) (setq #no1 ""))
    (setq #no2  (datocelda row col3))
    (if (not #no2) (setq #no2 ""))
    (setq #name (datocelda row col4))
    (setq #qty1 (datocelda row col5))
    (setq #qty2 (datocelda row col6))
    (setq #size (datocelda row col7))
    (setq xls_list (append xls_list (list (list #no1 sno #no1 #no2 #name #qty1 #qty2 #size))))
    (setq dno_list (append dno_list (list #no1)))
    (setq ##1 sno)
    (repeat (- 12 (strlen sno))
      (setq ##1 (strcat ##1 " "))
    )	
    (setq #dno_list (append #dno_list (list (strcat ##1 #no1))))
    (setq row (1+ row))
  )
  (vlax-invoke-method (vlax-get-property objExcel "ActiveWorkbook") "Close" :vlax-False)
  (TerminaExcel)
)  

(defun c:sym_ec()
  (setvar "cmdecho" 0)
  (load "w_factor")
  (command ".ucs" "w")
  (setq oldla (getvar "clayer"))
  (setq oldos (getvar "osmode"))
  (command ".zoom" "e")
  (setq ss_item (ssget "x" '((0 . "INSERT") (8 . "TEXT") (66 . 1))))
  (if (not ss_item) (progn (alert "圖面上沒有零件清單!") (exit)))
  (get_ec_excel)
  (if (not (setq ss_no (ssget "x" '((0 . "INSERT") (2 . "DRAWING-NO")))))
      (setq #dno "")
      (progn
	(setq n 0 #dno "" $dno "")
	(repeat (sslength ss_no)
	  (setq ent (ssname ss_no n))
	  (if (= $dno "") (setq $dno (cdr (assoc 1 (entget (entnext ent))))))
	  (if (/= $dno "") (setq #dno (substr $dno 1 9)))
          (setq n (1+ n))
	)
      )
  )
  (if (= #dno "")
      (if (not (setq ss_no (ssget "x" '((0 . "INSERT") (2 . "A#BORDER")))))
	  (setq #dno "")
	  (progn
	    (setq ent (ssname ss_no 0))
	    (setq blk (strcase (cdr (assoc 2 (entget ent)))))
	    (setq obj (vlax-ename->vla-object ent)) 
            (vla-GetBoundingBox obj 'ptmin 'ptmax)
            (setq ptmin (vlax-safearray->list ptmin))
            (setq ptmax (vlax-safearray->list ptmax))
	    (setq p1 (list (car ptmax) (cadr ptmin)))
	    (if (= blk "A0BORDER")
	        (setq p2 (list (- (car p1) 84) (+ (cadr p1) 18.45)))
	        (setq p2 (list (- (car p1) 74) (+ (cadr p1) 18.45)))
	    )  
            (setq sst (ssget "w" p1 p2 '((0 . "TEXT"))))
	    (if (not sst)
	        (setq #dno "")
	        (setq #dno (substr (cdr (assoc 1 (entget (ssname sst 0)))) 1 9))
	    )
	  )
       )	
  )
  (setq dcl_id (load_dialog "get_bom.dcl"))
  (new_dialog "get_bom" dcl_id)
  (set_tile "dno" #dno)
  (fill_list "$dno" #dno_list)
  (if (/= #dno "") (focus_item))
  (action_tile "dno"   "(focus_item)")
  (action_tile "$dno"   "(set_tile \"dno\" (nth (atoi $value) dno_list))")
  (action_tile "accept" "(setq #dno (get_tile \"dno\")) (done_dialog 1)")
  (action_tile "cancel" "(done_dialog 0)")
  (setq ans (start_dialog))
  (if (= ans 1) (sym_ec))
  (setvar "clayer" oldla)
  (setvar "osmode" oldos)
  (setvar "attdia" 1)
  (princ)
)

(defun sym_ec()
  (setq #dno (vl-string-right-trim " " #dno))
  (setq ans_list (assoc #dno xls_list))
  (if (not ans_list)
      (progn (alert "找不到此圖號的設變內容!") (exit))
      (progn
	(setq xls_list (member ans_list xls_list))
	(setq pstep (cadar xls_list))
	(setq xls_list (cdr xls_list)) ;;此號碼之後的資料
	(setq new_list nil)
	(setq go t m 0)
        (while (and go (< m (length xls_list)))
	  (setq cstep (nth 1 (setq x (nth m xls_list))))
	  (if (<= (strlen cstep) (strlen pstep))
	      (setq go nil)
	      (progn
	        (setq $n (vl-string-search pstep cstep))
	        (if (= $n 0)
                    (if (not (vl-string-search "-" (substr cstep (+ (strlen pstep) 2))))
	                (setq new_list (append new_list (list x)))
	            )
	        )
	      )	
	  )
	  (setq m (1+ m))
	) ; end while
      )
  )
  ;(TerminaExcel)
  (if new_list
     (progn
        (get_att_list)
        (setvar "osmode" 0)
        (setvar "attdia" 0)
        (setq err_msg "" err_del "" err_add "" err_chg "")
        (if (not (tblsearch "LAYER" "EC")) (command ".layer" "n" "EC" ""))
        (if (setq ss (ssget "x" '((0 . "LWPOLYLINE") (8 . "EC")))) (command ".erase" ss ""))
        (if (setq ss (ssget "x" '((0 . "INSERT") (8 . "EC")))) (command ".erase" ss ""))
        (foreach x new_list
           (cond ((= (strcase (nth 0 x)) "ADDPART") (add_part x))
	         ((= (strcase (nth 3 x)) "DEL")     (del_part x))
	         (t                                 (chg_part x))
           )
        )
        (if (or (/= err_add "") (/= err_del "") (/= err_add "")) (show_msg) (alert "完成。"))
     )  
  );end if
)

;;================================================================================================================
(defun show_msg()
  (if (/= err_add "") (setq err_msg (strcat err_msg "新增錯誤(已存在設變後零件):\n" err_add "\n")))
  (if (/= err_del "") (setq err_msg (strcat err_msg "刪除錯誤(找不到設變前零件):\n" err_del "\n")))
  (if (/= err_chg "") (setq err_msg (strcat err_msg "進號錯誤(找不到設變前零件):\n" err_chg "\n")))
  (alert err_msg)
)

;;================================================================================================================ 
(defun add_part(new_data)
  ;;(setq new_data (nth 1 new_list))
  (setq #dno (nth 3 new_data))
  (if (assoc #dno all_att_list)
      (setq err_add (strcat err_add #dno "\n"))
      (progn
        (setq last_data (nth (1- (length all_att_list)) all_att_list))
        (setq #no (itoa (1+ (atoi (nth 1 last_data)))))
        (setq #dno (nth 3 new_data))
        (setq #val (nth 4 new_data))
        (setq #qty (rtos (nth 6 new_data) 2 0))
        (setq #size (nth 7 new_data))
        (setq ent (nth 5 last_data))
        (setvar "osmode" 0)
        (setq pt (polar (cdr (assoc 10 (entget ent))) (* 0.5 pi) 8))
        (setvar "clayer" "EC")
        (command ".insert" "DNO_EC" pt 1 1 0)
        (setvar "clayer" "TEXT")
        (command ".insert" "BOM_item" pt 1 1 0 #no #dno #val #qty #size)
        (if (> (setq #len (strlen #val)) 15) (chg_factor))
        (setq all_att_list (append all_att_list (list (list #dno #no #val #qty #size (entlast)))))
     )
  );end if
)  

;;================================================================================================================ 
(defun del_part(new_data)
  ;;(setq new_data (nth 2 new_list))
  (setq old_data (assoc (setq #dno (nth 0 new_data)) all_att_list))
  (if (not old_data)
      ;(alert (strcat "找不到要刪除的編號: " #dno ))
      (setq err_del (strcat err_del #dno "\n"))
      (progn
	(setq ent (nth 5 old_data))
	(setq pt (cdr (assoc 10 (entget ent))))
	(setq pt2 (list (- (car pt) 70) (+ (cadr pt) 8)))
        (setq sst (ssget "w" pt pt2 '((0 . "TEXT") (8 . "TEXT"))))
	(if sst (command ".erase" sst ""))
	(setq $ent (entnext ent))
	(setq data (entget $ent))
	(while (= (cdr (assoc 0 data)) "ATTRIB")
	  (setq tag (cdr (assoc 2 data)))
	  (setq old (assoc 1 data))
	  (cond ((= tag "DNO")  (entmod (subst (cons 1 "")  old data)))
		((= tag "NAME") (entmod (subst (cons 1 "")  old data)))
		((= tag "QTY")  (entmod (subst (cons 1 "")  old data)))
		((= tag "SIZE") (entmod (subst (cons 1 "")  old data)))
	  )
	  (setq $ent (entnext $ent))
	  (setq data (entget $ent))
	)  
	;(if (> (setq #len (strlen #val)) 18) (chg_factor2))
	(setvar "clayer" "EC")
        (command ".insert" "DNO_EC" pt 1 1 0)
	(LM:setdynpropvalue (vlax-ename->vla-object ent) "可見性1" "全部畫斜線")
      )
   );end if
)

(defun LM:setdynpropvalue ( blk prp val )
    (setq prp (strcase prp))
    (vl-some
       '(lambda ( x )
            (if (= prp (strcase (vla-get-propertyname x)))
                (progn
                    (vla-put-value x (vlax-make-variant val (vlax-variant-type (vla-get-value x))))
                    (cond (val) (t))
                )
            )
        )
        (vlax-invoke blk 'getdynamicblockproperties)
    )
)
;;================================================================================================================ 
(defun chg_part(new_data)
  ;(setq new_data (nth 0 new_list))
  (setq old_data (assoc (setq #dno (nth 0 new_data)) all_att_list))
  (if (not old_data)
      ;;(alert (strcat "找不到設變前編號: " #dno ))
      (setq err_chg (strcat err_chg #dno "\n"))
      (progn
	(setq ent (nth 5 old_data))
	(setq pt (cdr (assoc 10 (entget ent))))
	(setq #dno (nth 3 new_data))
	(setq #val (nth 4 new_data))
        (setq #qty (rtos (nth 6 new_data) 2 0))
        (setq #size (nth 7 new_data))
	(setq $ent (entnext ent))
	(setq data (entget $ent))
	(while (= (cdr (assoc 0 data)) "ATTRIB")
	  (setq tag (cdr (assoc 2 data)))
	  (setq old (assoc 1 data))
	  (cond ((= tag "DNO")  (entmod (subst (cons 1 #dno)  old data)))
		((= tag "NAME") (entmod (subst (cons 1 #val)  old data)))
		((= tag "QTY")  (entmod (subst (cons 1 #qty)  old data)))
		((= tag "SIZE") (entmod (subst (cons 1 #size) old data)))
	  )
	  (setq $ent (entnext $ent))
	  (setq data (entget $ent))
	)  
	(if (> (setq #len (strlen #val)) 15) (chg_factor2))
	(setvar "clayer" "EC")
        (command ".insert" "DNO_EC" pt 1 1 0)
      )
   );end if
)

(defun c:2xls()
  (load "w_factor")
  (setq ss_item (ssget "x" '((0 . "INSERT") (8 . "TEXT") (66 . 1))))
  (if (not ss_item) (progn (alert "圖面上沒有零件清單!") (exit)))
  (get_att_list)
  ;(setq path (getvar "dwgprefix"))
  (setq path excel_path)
  (vl-mkdir path)
  (setq dwg (getvar "dwgname"))
  (setq xls (vl-filename-base dwg))
  (setq #file1 (findfile "TEMPLATE.xls"))
  (setq #file2 (strcat path xls ".xls"))
  (if (findfile #file2) (vl-file-delete #file2))
  (vl-file-copy #file1 #file2)
  (setq xls_file #file2)
  (IniciaExcel2)
  (setq row 2)  ;;4->6
  (foreach data all_att_list
     (vlax-put-property ObjCells 'item row 1  (nth 1 data))
     (vlax-put-property ObjCells 'item row 2  (nth 0 data))
     (vlax-put-property ObjCells 'item row 3  (nth 2 data))
     (if (/= (setq #3 (nth 3 data)) "")
         (vlax-put-property ObjCells 'item row 4 (atoi #3))
     )
     (vlax-put-property ObjCells 'item row 5  (nth 4 data))
     (setq row (1+ row))
   )
   (vlax-invoke-method ObjCurrWorkbooks "Save")
   (vlax-invoke-method ObjCurrWorkbooks "Close")
   (vlax-invoke-method ObjExcel "Quit")
   (TerminaExcel)
   (alert (strcat "匯出檔案:\n" #file2))
   (princ)
)


(defun sel_item()
  (while (not (setq ent (entsel "\n選擇要刪除的項目: "))))
  (setq ent (car ent))
  (setq data (entget ent))
  (if (/= (cdr (assoc 0 data)) "INSERT")
      (progn
	(alert "選擇的物件不是零件清單!")
	(sel_item)
      )
      (if (/= (strcase (vla-get-EffectiveName (vlax-ename->vla-object ent))) "BOM_ITEM")
	  (progn
	    (alert "選擇的物件不是零件清單!")
	    (sel_item)
          )
      )
  )  
)   

  

(defun del_item()
  (setq ss (ssget "x" '((0 . "INSERT") (2 . "DNO_EC"))))
  (if ss
     (progn
       (initget 6 "Yes No")
       (setq ans (getkword "\n設變標示是否刪除? <Yes>/No: "))
       (if (or (not ans) (= ans "Yes"))
	   (command ".erase" ss "")
       )
     )
  )
  (setq ss_item (ssget "x" '((0 . "INSERT") (8 . "TEXT") (66 . 1))))
  (get_att_list)
  (setvar "osmode" 0)
  (foreach x all_att_list
    (setq chk_no (atoi (nth 1 x)))
    (setq ent (nth 5 x))
    (cond ((= del_no chk_no) (entdel ent))
	  ((> del_no chk_no) t)
	  ((< del_no chk_no)
	   (setq data (entget (entnext ent)))
	   (setq old (assoc 1 data))
	   (setq new (cons 1 (itoa (1- chk_no))))
	   (entmod (subst new old data))
	   (setq data (entget ent))
	   (setq p1 (cdr (assoc 10 data)))
	   (setq p2 (polar p1 (* 1.5 pi) 8))
	   ;(entmod (subst (cons 10 p2) (cons 10 p1) data)))
	   (command ".move" ent "" p1 p2))
    )
  )
  (setvar "osmode" oldos)
  ;(command ".attsync" "n" "bom_item")
)

(defun c:txt2bom()
  (load "w_factor")
  (setvar "cmdecho" 0)
  (if (tblsearch "VIEW" "temp")
      (progn
        (command ".view" "d" "temp")
        (command ".view" "s" "temp") 
      )
      (command ".view" "s" "temp")
  )
  (setq oldos (getvar "osmode"))
  (setq oldla (getvar "clayer"))
  (setvar "osmode" 33)
  (initget 7)
  (setq p1 (getpoint "\n選擇第 1 列左下角點: "))
  (initget 7)
  (setq p2 (getpoint "\n選擇最後列右上角點: "))
  (initget 7)
  (setq h (getdist "\n列高: "))
  (command ".zoom" "w" p1 p2)
  (setvar "osmode" 0)
  (setq p01 p1)
  ;(setq p2 (list (+ (car p1) 120) (+ (cadr p1) h)))
  (setq p02 (polar (polar p01 0 10) (* 0.5 pi) h))
  (setq all_list nil)
  (while (or (setq ss (ssget "w" p01 p02 '((0 . "TEXT")))) (setq ss2 (ssget "w" (polar p01 0 10) (polar p02 0 120) '((0 . "TEXT")))))
    (setq str_list nil pt1 p01 pt2 p02)
    (setq m 0)
    (repeat 7
       (setq ss (ssget "w" pt1 pt2 '((0 . "TEXT"))))
       (if (and (= m 0) (not ss) (= #1st 0))
	   (setq ss (ssget "w" pt1 (polar pt2 (* 0.5 pi) h) '((0 . "TEXT"))) #1st 1)
	   (if (= m 0) (setq #1st 0))
       )	 
       (if (and (= m 3) (not ss))(setq ss (ssget "w" pt1 (polar pt2 (* 0.5 pi) h) '((0 . "TEXT")))))
       (setq txt "")
       (if ss
	 (if (or (= m 0) (= m 1)(= m 2) (= m 3) (= m 6))
             (setq txt (cdr (assoc 1 (entget (ssname ss 0)))))
	     (progn  
	       (setq n 0 $tmp_list nil)
	       (repeat (sslength ss)
                 (setq data (entget (ssname ss n)))
		 (setq $txt (cdr (assoc 1 data)))
		 (setq $y   (cdr (assoc 10 data)))
		 (setq $tmp_list (append $tmp_list (list (list $y $txt))))
                 ;(setq txt (strcat txt "\n" (cdr (assoc 1 data))))
	         (setq n (1+ n))
	       )
	       (vl-sort $tmp_list (function (lambda (y1 y2) (> (cadar y1) (cadar y2)))))
	       (foreach $tmp $tmp_list
		  (setq txt (strcat txt "\n" (cadr $tmp)))
	       )	 
	       (setq txt (substr txt 2))
	     )
	  )
       )
       (setq str_list (append str_list (list txt)))
       (setq x_list '(10 50 50 10 30 30 10 0))
       (setq dx1 (nth m x_list)
	     dx2 (nth (1+ m) x_list))
       (setq pt1 (polar pt1 0 dx1))
       (setq pt2 (polar pt2 0 dx2))
       (setq m (1+ m))
    )
    (setq str_list (append str_list (list #1st)))
    (setq all_list (append all_list (list str_list)))
    (setq p01 (polar p01 (* 0.5 pi) h)
	  p02 (polar p02 (* 0.5 pi) h))             
      ;(setq n (1+ n))
  )	   
  (if all_list (txt2bom))
  (setvar "clayer" oldla)
  (setvar "osmode" oldos)
  (princ)
)

(defun c:txt2bom2()
  (load "w_factor")
  (setvar "cmdecho" 0)
  (if (tblsearch "VIEW" "temp")
      (progn
        (command ".view" "d" "temp")
        (command ".view" "s" "temp") 
      )
      (command ".view" "s" "temp")
  )
  (setq oldos (getvar "osmode"))
  (setq oldla (getvar "clayer"))
  (setvar "osmode" 33)
  (initget 7)
  (setq p1 (getpoint "\n選擇第 1 列左下角點: "))
  (initget 7)
  (setq p2 (getpoint "\n選擇最後列右上角點: "))
  (initget 7)
  (setq h (getdist "\n列高: "))
  (prompt "\n由左至右取得標題欄位的每個左上角點...")
  (initget 7)
  (setq p3 (getpoint p1 "\n選擇 DWG.NO. 左上角點: "))
  (setq w1 (distance p1 p3))
  (initget 7)
  (setq p4 (getpoint p3 "\n選擇 NAME 左上角點: "))
  (setq w2 (distance p3 p4))
  (initget 7)
  (setq p5 (getpoint p4 "\n選擇 QTY. 左上角點: "))
  (setq w3 (distance p4 p5))
  (initget 7)
  (setq p6 (getpoint p5 "\n選擇 MATERIAL 左上角點: "))
  (setq w4 (distance p5 p6))
  (initget 7)
  (setq p7 (getpoint p6 "\n選擇 REMARKS 左上角點: "))
  (setq w5 (distance p6 p7))
  (initget 7)
  (setq p8 (getpoint p7 "\n選擇 DWG. 左上角點: "))
  (setq w6 (distance p7 p8))
  (setq w7 (- (car p2) (car p8))) 
  (command ".zoom" "w" p1 p2)
  (setvar "osmode" 0)
  (setq p01 p1)
  (setq p02 (polar (polar p01 0 W1) (* 0.5 pi) h))
  (setq all_list nil #1st 0)
  (while (or (setq ss (ssget "w" p01 p02 '((0 . "TEXT")))) (setq ss2 (ssget "w" (polar p01 0 10) (polar p02 0 120) '((0 . "TEXT")))))
    (setq str_list nil pt1 p01 pt2 p02)
    (setq m 0)
    (repeat 7
       (setq ss (ssget "w" pt1 pt2 '((0 . "TEXT"))))
       (if (and (= m 0) (not ss) (= #1st 0))
	   (setq ss (ssget "w" pt1 (polar pt2 (* 0.5 pi) h) '((0 . "TEXT"))) #1st 1)
	   (if (= m 0) (setq #1st 0))
       )	 
       (if (and (= m 3) (not ss))(setq ss (ssget "w" pt1 (polar pt2 (* 0.5 pi) h) '((0 . "TEXT")))))
       (setq txt "")
       (if ss
	 (if (or (= m 0) (= m 1)(= m 2) (= m 3) (= m 6))
             (setq txt (cdr (assoc 1 (entget (ssname ss 0)))))
	     (progn  
	       (setq n 0 $tmp_list nil)
	       (repeat (sslength ss)
                 (setq data (entget (ssname ss n)))
		 (setq $txt (cdr (assoc 1 data)))
		 (setq $y   (cdr (assoc 10 data)))
		 (setq $tmp_list (append $tmp_list (list (list $y $txt))))
                 ;(setq txt (strcat txt "\n" (cdr (assoc 1 data))))
	         (setq n (1+ n))
	       )
	       (setq $tmp_list (vl-sort $tmp_list (function (lambda (y1 y2) (> (cadar y1) (cadar y2))))))
	       (foreach $tmp $tmp_list
		  (setq txt (strcat txt "\n" (cadr $tmp)))
	       )
	       (setq txt (substr txt 2))
	     )  
	  )
       )
       (setq str_list (append str_list (list txt)))
       (setq x_list (list w1 w2 w3 w4 w5 w6 w7 0))
       (setq dx1 (nth m x_list)
	     dx2 (nth (1+ m) x_list))
       (setq pt1 (polar pt1 0 dx1))
       (setq pt2 (polar pt2 0 dx2))
       (setq m (1+ m))
    )
    (setq str_list (append str_list (list #1st)))
;;;    (setq #1st (* -1 #1st))
    (setq all_list (append all_list (list str_list)))
    (setq p01 (polar p01 (* 0.5 pi) h)
	  p02 (polar p02 (* 0.5 pi) h))
    ;(setq pt1 p01 pt2 p02)
      ;(setq n (1+ n))
  )	   
  (if all_list (txt2bom))
  (setvar "clayer" oldla)
  (setvar "osmode" oldos)
  (princ)
)


(defun txt2bom()
  (load "w_factor2")
  (command ".view" "r" "temp")
  (initget 7)
  (setq pt (getpoint "\n插入點(右下點): "))
  (if (tblsearch "LAYER" "TEXT")
      (setvar "clayer" "TEXT")
      (command ".layer" "m" "TEXT" "c" 3 "TEXT" "")
  )
  (setvar "attdia" 0)
  (command ".insert" "BOM_Title" pt 1 1 0)
  (setvar "textstyle" "BOM")
  (setq pt (polar pt (* 0.5 pi) 8))
  (setq #n 1 #1st t old_blk "BOM_ITEM")
  (foreach item all_list
    (if (= (setq #size (vl-string-right-trim " " (nth 6 item))) "") (setq #size "X"))
    (if (= (nth 7 item) 1)
        (setq #blk "BOM_ITEM2")
        (setq #blk "BOM_ITEM")
    )
    (setq #no  (vl-string-right-trim " " (nth 0 item)))
    (setq #dno (vl-string-right-trim " " (nth 1 item)))
    (setq #val (vl-string-right-trim " " (nth 2 item)))
    (setq #qty (vl-string-right-trim " " (nth 3 item)))
    (if (= old_blk "BOM_ITEM2") (setq #qty ""))
    (command ".insert" #blk pt 1 1 0 #no #dno #val #qty #size)
;;;	     (vl-string-right-trim " " (nth 0 item))
;;;	     (setq #dno (vl-string-right-trim " " (nth 1 item)))
;;;	     (setq #val (vl-string-right-trim " " (nth 2 item)))
;;;	     (vl-string-right-trim " " (nth 3 item))
;;;	     #size)
    (setq old_blk #blk)
    (setq @ent (entlast))
    (if (> (setq #len (strlen #val)) 15) (chg_factor))
    (setq pt1 (list (+ (car (setq tmp (polar pt pi 70))) 0.45) (+ (cadr tmp) 2)))
    (setq pt2 (list (+ (car (setq tmp (polar pt pi 41))) 0.45) (+ (cadr tmp) 2)))	     
    (if (/= (setq #val (vl-string-right-trim " " (nth 4 item))) "")
        ;(progn (command ".text" pt1 5 0 #val) (setq $m t))
        (progn (write_text pt1) (setq $m t))
        (setq $m nil)
    )  
    (if (/= (setq #val (vl-string-right-trim " " (nth 5 item))) "")
        ;(progn (command ".text" pt2 5 0 #val) (setq $r t))
        (progn (write_text2 pt2) (setq $r t))
        (setq $r nil)
    )
    (cond ((and $m $r (/= #dno "")) (LM:setdynpropvalue (vlax-ename->vla-object @ent) "可見性1" "填寫Material + Remarks"))
	  ((and $m    (/= #dno "")) (LM:setdynpropvalue (vlax-ename->vla-object @ent) "可見性1" "填寫Material"))
	  ((and $r    (/= #dno "")) (LM:setdynpropvalue (vlax-ename->vla-object @ent) "可見性1" "填寫Remarks"))
          ((and $m $r (= #dno "")) (LM:setdynpropvalue (vlax-ename->vla-object @ent) "可見性1" "填寫Material + Remarks_無DNO"))
	  ((and $m    (= #dno "")) (LM:setdynpropvalue (vlax-ename->vla-object @ent) "可見性1" "填寫Material_無DNO"))
	  ((and $r    (= #dno "")) (LM:setdynpropvalue (vlax-ename->vla-object @ent) "可見性1" "填寫Remarks_無DNO"))	  
          (t nil)
    )	  
    (setq pt (polar pt (* 0.5 pi) 8))
  )
)

(defun write_text($pt)
  (setq $pt (polar $pt 0 14.5))
  (if (setq $n (vl-string-search "\n" #val))
      (progn
	(setq str1 (substr #val 1 $n))
	(setq str2 (substr #val (+ $n 2)))
	(setq $pt (polar $pt (* 1.5 pi) 1.65))
	(command ".text" "c" $pt 3 0 str2)
	(setq #len (strlen str2))
	(if (vl-string-search "%%" str2) (setq #len (- #len 2)))
	;(chg_factor3)
	(setq $pt (polar $pt (* 0.5 pi) 4))
	(command ".text" "c" $pt 3 0 str1)
	(setq #len (strlen str1))
	(if (vl-string-search "%%" str1) (setq #len (- #len 2)))
	;(chg_factor3)
      )
      (progn
	(setq str #val)
	(command ".text" "c" $pt 5 0 str)
	(setq #len (strlen str))
	(if (vl-string-search "%%" str) (setq #len (- #len 2)))
	(chg_factor3)
      )
  )
)

(defun write_text2($pt)
  (setq $pt (polar $pt 0 14.5)) ;至中
  (if (setq $n (vl-string-search "\n" #val))
      (progn
	(setq str1 (substr #val 1 $n))
	(setq str2 (substr #val (+ $n 2)))
	(setq $pt (polar $pt (* 1.5 pi) 1.65))
	(command ".text" "c" $pt 3 0 str2)
	(setq #len (strlen str2))
	(if (vl-string-search "%%" str2) (setq #len (- #len 2)))
	;(chg_factor3)
	(setq $pt (polar $pt (* 0.5 pi) 4))
	(command ".text" "c" $pt 3 0 str1)
	(setq #len (strlen str1))
	(if (vl-string-search "%%" str1) (setq #len (- #len 2)))
	;(chg_factor3)
      )
      (progn
	(setq str #val)
	(command ".text" "c" $pt 5 0 str)
	(setq #len (strlen str))
	(if (vl-string-search "%%" str)
	    (progn
	      (setq #len (- #len 2))
	      (chg_factor3)
	    )
	)  
	;(chg_factor3)
      )
  )
)
